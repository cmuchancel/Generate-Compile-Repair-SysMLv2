package UnitSystemLibrary {
    private import ScalarValues::*;

    enum def QuantityKind {
        enum length;
        enum mass;
        enum time;
        enum electricCurrent;
        enum thermodynamicTemperature;
        enum amountOfSubstance;
        enum luminousIntensity;
        enum planeAngle;
        enum solidAngle;
        enum frequency;
        enum force;
        enum pressure;
        enum energy;
        enum power;
        enum electricCharge;
        enum voltage;
        enum capacitance;
        enum electricResistance;
        enum electricConductance;
        enum magneticFlux;
        enum magneticFluxDensity;
        enum inductance;
        enum temperature;
        enum area;
        enum volume;
        enum velocity;
        enum acceleration;
        enum angularVelocity;
        enum angularAcceleration;
        enum density;
        enum surfaceDensity;
        enum specificVolume;
        enum luminance;
    }

    enum def UnitSystem {
        enum ISQ;
        enum USCustomaryUnits;
    }

    part def Unit {
        attribute name : String;
        attribute symbol : String;
        attribute quantityKind : QuantityKind;
        attribute conversionFactorToBase : Real;
        attribute offsetToBase : Real = 0.0;
        attribute unitSystem : UnitSystem;
    }

    part def UnitConverter {
        attribute sourceUnit : Unit;
        attribute targetUnit : Unit;
        attribute conversionFactor : Real;
        attribute offset : Real = 0.0;

        port convert : Real;
    }

    part def UnitLibrary {
        attribute units : Unit[0..*];
        attribute converters : UnitConverter[0..*];

        port addUnit : Unit;
        port removeUnit : Unit;
        port findUnit : Unit;
        port convertValue : Real;
    }

    part isqLibrary : UnitLibrary {
        attribute units : Unit[0..*] = (
            Unit meter {
                attribute name = "meter";
                attribute symbol = "m";
                attribute quantityKind = QuantityKind::length;
                attribute conversionFactorToBase = 1.0;
                attribute unitSystem = UnitSystem::ISQ;
            },
            Unit kilogram {
                attribute name = "kilogram";
                attribute symbol = "kg";
                attribute quantityKind = QuantityKind::mass;
                attribute conversionFactorToBase = 1.0;
                attribute unitSystem = UnitSystem::ISQ;
            },
            Unit second {
                attribute name = "second";
                attribute symbol = "s";
                attribute quantityKind = QuantityKind::time;
                attribute conversionFactorToBase = 1.0;
                attribute unitSystem = UnitSystem::ISQ;
            },
            Unit ampere {
                attribute name = "ampere";
                attribute symbol = "A";
                attribute quantityKind = QuantityKind::electricCurrent;
                attribute conversionFactorToBase = 1.0;
                attribute unitSystem = UnitSystem::ISQ;
            },
            Unit kelvin {
                attribute name = "kelvin";
                attribute symbol = "K";
                attribute quantityKind = QuantityKind::thermodynamicTemperature;
                attribute conversionFactorToBase = 1.0;
                attribute unitSystem = UnitSystem::ISQ;
            },
            Unit mole {
                attribute name = "mole";
                attribute symbol = "mol";
                attribute quantityKind = QuantityKind::amountOfSubstance;
                attribute conversionFactorToBase = 1.0;
                attribute unitSystem = UnitSystem::ISQ;
            },
            Unit candela {
                attribute name = "candela";
                attribute symbol = "cd";
                attribute quantityKind = QuantityKind::luminousIntensity;
                attribute conversionFactorToBase = 1.0;
                attribute unitSystem = UnitSystem::ISQ;
            }
        );
    }

    part usCustomaryLibrary : UnitLibrary {
        attribute units : Unit[0..*] = (
            Unit inch {
                attribute name = "inch";
                attribute symbol = "in";
                attribute quantityKind = QuantityKind::length;
                attribute conversionFactorToBase = 0.0254;
                attribute unitSystem = UnitSystem::USCustomaryUnits;
            },
            Unit foot {
                attribute name = "foot";
                attribute symbol = "ft";
                attribute quantityKind = QuantityKind::length;
                attribute conversionFactorToBase = 0.3048;
                attribute unitSystem = UnitSystem::USCustomaryUnits;
            },
            Unit yard {
                attribute name = "yard";
                attribute symbol = "yd";
                attribute quantityKind = QuantityKind::length;
                attribute conversionFactorToBase = 0.9144;
                attribute unitSystem = UnitSystem::USCustomaryUnits;
            },
            Unit mile {
                attribute name = "mile";
                attribute symbol = "mi";
                attribute quantityKind = QuantityKind::length;
                attribute conversionFactorToBase = 1609.344;
                attribute unitSystem = UnitSystem::USCustomaryUnits;
            },
            Unit poundMass {
                attribute name = "pound-mass";
                attribute symbol = "lbm";
                attribute quantityKind = QuantityKind::mass;
                attribute conversionFactorToBase = 0.45359237;
                attribute unitSystem = UnitSystem::USCustomaryUnits;
            },
            Unit ounce {
                attribute name = "ounce";
                attribute symbol = "oz";
                attribute quantityKind = QuantityKind::mass;
                attribute conversionFactorToBase = 0.028349523125;
                attribute unitSystem = UnitSystem::USCustomaryUnits;
            },
            Unit second {
                attribute name = "second";
                attribute symbol = "s";
                attribute quantityKind = QuantityKind::time;
                attribute conversionFactorToBase = 1.0;
                attribute unitSystem = UnitSystem::USCustomaryUnits;
            }
        );
    }

    part converter : UnitConverter {
        attribute sourceUnit = usCustomaryLibrary.units[0];
        attribute targetUnit = isqLibrary.units[0];
        attribute conversionFactor = 0.0254;
    }

    connect usCustomaryLibrary.convertValue to converter.convert;
    connect converter.convert to isqLibrary.convertValue;
}
